// mAF — the mbaigo Arrowhead Framework library in SysML v2.
//
// GENERATED by cmd/mafgen from maf-frame.sysml, afo-maf-mapping.tsv and
// kgrapher/ontologies/afo.ttl — edit those and run `go generate`, not this.
//
// Encodes the core vocabulary of an Arrowhead local cloud so that concrete
// models (emitted by the modeler) can specialise from typed abstractions
// instead of re-inventing Arrowhead semantics inline. mAF is the SysML v2
// sibling of the AFO OWL ontology: the same concepts seen from a structural
// and behavioural angle, rather than a reasoning angle. Use mAF for
// composition, ports, connections, and behaviour; use AFO for class
// reasoning, property chains, and semantic queries.
//
// Intended use — concrete types specialise from mAF abstractions:
//     part def 'thermostatSystem'                 :> ArrowheadSystem    { ... }
//     part def 'serviceregistrarSystem'           :> ServiceRegistrar   { ... }
//     part def 'thermostat_controller_1UnitAsset' :> UnitAsset          { ... }
//     part def 'alphaCloudDef'                    :> LocalCloud         { ... }

package mAF {

    // The SysML v2 standard library defines primitive datatypes under
    // ScalarValues. Without these imports, 'String' and 'Integer' are
    // unresolved references in tools that follow the spec strictly
    // (e.g. the Eclipse SysML v2 IDE).
    private import ScalarValues::String;
    private import ScalarValues::Integer;
    private import ScalarValues::Boolean;

    // ── Abstract action definitions ──────────────────────────────────────────
    // The three elementary actions a unit asset can perform: read a consumed
    // service (GetState), compute a control decision (Compute), and write
    // to a consumed service (SetState). Behaviour defs emitted by the
    // modeler chain these actions with 'first … then …' pairs.
    abstract action def GetState { attribute mode : Mode = Mode::'get'; }
    abstract action def SetState { attribute mode : Mode = Mode::'set'; }
    abstract action def Compute  { attribute mode : Mode = Mode::'do'; }

    // ── Mission ─────────────────────────────────────────────────────────────
    // What a unit asset is for, and the axis the authorizer decides on. Closed,
    // as it is in the framework (components.Missions); the modeler's tests
    // fail if the two lists differ. Quoted, because 'state' and 'event' are
    // SysML v2 keywords.
    enum def Mission {
        enum 'measurement';
        enum 'actuation';
        enum 'state';
        enum 'event';
        enum 'aggregation';
        enum 'logging';
        enum 'control';
        enum 'transaction';
        enum 'core';
    }

    // ── Definitions from AFO ────────────────────────────────────────────────
    // Generated from kgrapher/ontologies/afo.ttl and afo-maf-mapping.tsv by
    // cmd/mafgen; each definition's doc is AFO's comment for the term.
    abstract part def ArrowheadSystem {
        doc
        /*
         * An Arrowhead System: the primary participant in a local cloud. Consists
         * of at least one Husk (runtime container) and at least one UnitAsset
         * (functional component).
         */
        attribute name : String;
        attribute host : String;
        attribute endpoints : Endpoint[0..*];
        attribute posture : SecurityPosture[0..1];
        part externalAttachments : ExternalAttachment[0..*];
    }

    abstract part def CoreSystem :> ArrowheadSystem {
        doc
        /*
         * A system that mediates the cloud rather than doing its work: the ones an
         * application system finds already there. Gathered under one class so a
         * query can ask what infrastructure a cloud is running without naming
         * each.
         */
    }

    abstract part def ServiceRegistrar :> CoreSystem {
        doc
        /*
         * A core Arrowhead System responsible for registering and discovering
         * services within the local cloud. Identified by the system name
         * 'serviceregistrar'.
         */
    }

    abstract part def Orchestrator :> CoreSystem {
        doc
        /*
         * A core Arrowhead System responsible for service orchestration —
         * matching service consumers to appropriate service providers within the
         * local cloud.
         */
    }

    abstract part def CertificateAuthority :> CoreSystem {
        doc
        /*
         * A core Arrowhead System responsible for issuing and managing
         * certificates that enable secure communication within a SecureLocalCloud.
         */
    }

    abstract part def Authorizer :> CoreSystem {
        doc
        /*
         * Decides what a certified system may do, minting the per-action tokens a
         * provider checks. A cloud that names none has authentication without
         * authorization, which is a decision rather than an omission.
         */
    }

    abstract part def MaitreD :> CoreSystem {
        doc
        /*
         * Attests the binaries running on its own host: it hashes the executable
         * behind a process and answers the CA, which signs nothing without it. One
         * per host, and it can only speak for processes of its own user.
         */
    }

    abstract part def UnitAsset {
        doc
        /*
         * The functional component of an Arrowhead System. A UnitAsset
         * encapsulates the domain logic and must provide at least one Service. It
         * may also consume services from other Systems.
         */
        attribute mission : Mission;
        attribute functionalLocation : String[0..*];
    }

    part def Host {
        doc
        /*
         * A physical or virtual machine that hosts Endpoints and runs Husks.
         */
        attribute name : String;
        attribute ipAddress : String[*];
    }

    abstract part def LocalCloud {
        doc
        /*
         * An Arrowhead local cloud: a set of Systems within a defined
         * administrative domain. Must contain at least one Orchestrator and one
         * ServiceRegistrar.
         */
        attribute name : String;
    }

    abstract port def ServicePort {
        doc
        /*
         * A service offered or consumed within the Arrowhead framework. The
         * superclass of ProvidedService and ConsumedService.
         */
        attribute value : Quantities::ScalarQuantityValue[0..1];
        attribute qudtUnit : String[0..1];
        attribute qudtQuantityKind : String[0..1];
        attribute mode : Mode[0..1];
        attribute methods : String[0..*];
        attribute forms : String[0..*];
        attribute defaultForm : String[0..1];
        attribute registrationPeriod : ISQ::DurationValue[0..1];
        attribute subscribable : Boolean[0..1];
    }

    enum def Mode {
        doc
        /*
         * How a service is used: read a value, write one, or invoke an operation.
         * The authorizer maps a mode to the action a policy grants, so this is a
         * term access control depends on — which is the argument for declaring
         * it here rather than leaving it in a namespace nothing can interpret.
         */
        enum 'get';
        enum 'set';
        enum 'do';
    }

    attribute def Endpoint {
        doc
        /*
         * A network endpoint defined by at least one port and one protocol, hosted
         * on a Host. Used by a Husk to expose communication interfaces.
         */
        attribute protocol : String;
        attribute portNumber : Integer;
    }

    attribute def SecurityPosture {
        doc
        /*
         * The security a system actually presents at run time: whether it is
         * identified, what it will accept, and whom it trusts to say so.
         */
        attribute securityLevel : String;
        attribute namesCertificateAuthority : Boolean;
        attribute namesAuthorizer : Boolean;
        attribute isIdentified : Boolean;
        attribute canVerifyPeers : Boolean;
        attribute verifiesTokens : Boolean;
        attribute offersTLS : Boolean;
        attribute acceptsPlaintext : Boolean;
    }

    part def ExternalAttachment {
        doc
        /*
         * A service outside the local cloud that a system depends on: a database,
         * a broker, a field device. The cloud's own machinery — attestation,
         * mutual TLS, tokens — does not reach across this boundary, so what
         * protects the connection is whatever the adjacent protocol was configured
         * to do. Declared by the system, because only the system knows what it
         * attaches to. Nothing enforces the declaration: an undeclared attachment
         * is invisible, which is what every attachment was before this class
         * existed. A security posture that described only the inbound direction
         * let a graph overstate how protected a cloud was.
         */
        attribute name : String;
        attribute protocol : String[0..1];
        attribute isEncrypted : Boolean;
        attribute isAuthenticated : Boolean;
    }


    // ── Units the standard library lacks ────────────────────────────────────
    // Units the systems declare that are not in the SysML v2 Quantities and
    // Units library (release 2026-08), defined from it with the factors the
    // framework converts with (mbaigo usecases/qudt.go). Referenced by
    // mbaigo's usecases/sysml_units.go as mAF::<name>.
    attribute <ms> millisecond : ISQ::DurationUnit {
        :>> unitConversion : MeasurementReferences::ConversionByPrefix { :>> prefix = SIPrefixes::milli; :>> referenceUnit = SI::s; }
    }
    attribute <ftn> fortnight : ISQ::DurationUnit {
        :>> unitConversion : MeasurementReferences::ConversionByConvention { :>> referenceUnit = SI::s; :>> conversionFactor = 1209600; }
    }
    attribute <hPa> hectopascal : ISQ::PressureUnit {
        :>> unitConversion : MeasurementReferences::ConversionByPrefix { :>> prefix = SIPrefixes::hecto; :>> referenceUnit = SI::Pa; }
    }
    attribute <kPa> kilopascal : ISQ::PressureUnit {
        :>> unitConversion : MeasurementReferences::ConversionByPrefix { :>> prefix = SIPrefixes::kilo; :>> referenceUnit = SI::Pa; }
    }
    attribute <bar> bar : ISQ::PressureUnit {
        :>> unitConversion : MeasurementReferences::ConversionByConvention { :>> referenceUnit = SI::Pa; :>> conversionFactor = 1E5; }
    }
    attribute <mbar> millibar : ISQ::PressureUnit {
        :>> unitConversion : MeasurementReferences::ConversionByPrefix { :>> prefix = SIPrefixes::milli; :>> referenceUnit = bar; }
    }
    attribute <fur> furlong : ISQ::LengthUnit {
        :>> unitConversion : MeasurementReferences::ConversionByConvention { :>> referenceUnit = SI::m; :>> conversionFactor = 201.168; }
    }
    attribute <r> revolution : ISQ::AngularMeasureUnit {
        :>> unitConversion : MeasurementReferences::ConversionByConvention { :>> referenceUnit = SI::rad; :>> conversionFactor = 6.283185307179586; :>> isExact = false; }
    }
    attribute <gon> gon : ISQ::AngularMeasureUnit {
        :>> unitConversion : MeasurementReferences::ConversionByConvention { :>> referenceUnit = SI::rad; :>> conversionFactor = 1.5707963267948967E-2; :>> isExact = false; }
    }
    attribute <'%'> percent : MeasurementReferences::DimensionOneUnit {
        :>> unitConversion : MeasurementReferences::ConversionByConvention { :>> referenceUnit = MeasurementReferences::one; :>> conversionFactor = 1E-2; }
    }
    attribute <ppm> 'part per million' : MeasurementReferences::DimensionOneUnit {
        :>> unitConversion : MeasurementReferences::ConversionByConvention { :>> referenceUnit = MeasurementReferences::one; :>> conversionFactor = 1E-6; }
    }
    attribute <'r/min'> 'revolution per minute' : ISQ::AngularVelocityUnit = r / SI::min;
    attribute <'mm/h'> 'millimetre per hour' : ISQ::SpeedUnit = SI::mm / SI::h;
    attribute <'fur/ftn'> 'furlong per fortnight' : ISQ::SpeedUnit = fur / ftn;
}
