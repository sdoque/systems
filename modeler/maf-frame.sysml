// mAF — the mbaigo Arrowhead Framework library in SysML v2.
//
// GENERATED by cmd/mafgen from maf-frame.sysml, afo-maf-mapping.tsv and
// kgrapher/ontologies/afo.ttl — edit those and run `go generate`, not this.
//
// Encodes the core vocabulary of an Arrowhead local cloud so that concrete
// models (emitted by the modeler) can specialise from typed abstractions
// instead of re-inventing Arrowhead semantics inline. mAF is the SysML v2
// sibling of the AFO OWL ontology: the same concepts seen from a structural
// and behavioural angle, rather than a reasoning angle. Use mAF for
// composition, ports, connections, and behaviour; use AFO for class
// reasoning, property chains, and semantic queries.
//
// Intended use — concrete types specialise from mAF abstractions:
//     part def 'thermostatSystem'                 :> ArrowheadSystem    { ... }
//     part def 'serviceregistrarSystem'           :> ServiceRegistrar   { ... }
//     part def 'thermostat_controller_1UnitAsset' :> UnitAsset          { ... }
//     part def 'alphaCloudDef'                    :> LocalCloud         { ... }

package mAF {

    // The SysML v2 standard library defines primitive datatypes under
    // ScalarValues. Without these imports, 'String' and 'Integer' are
    // unresolved references in tools that follow the spec strictly
    // (e.g. the Eclipse SysML v2 IDE).
    private import ScalarValues::String;
    private import ScalarValues::Integer;
    private import ScalarValues::Boolean;

    // ── Abstract action definitions ──────────────────────────────────────────
    // The three elementary actions a unit asset can perform: read a consumed
    // service (GetState), compute a control decision (Compute), and write
    // to a consumed service (SetState). Behaviour defs emitted by the
    // modeler chain these actions with 'first … then …' pairs.
    abstract action def GetState { attribute mode : Mode = Mode::'get'; }
    abstract action def SetState { attribute mode : Mode = Mode::'set'; }
    abstract action def Compute  { attribute mode : Mode = Mode::'do'; }

    // ── Mission ─────────────────────────────────────────────────────────────
    // What a unit asset is for, and the axis the authorizer decides on. Closed,
    // as it is in the framework (components.Missions); the modeler's tests
    // fail if the two lists differ. Quoted, because 'state' and 'event' are
    // SysML v2 keywords.
    enum def Mission {
        enum 'measurement';
        enum 'actuation';
        enum 'state';
        enum 'event';
        enum 'aggregation';
        enum 'logging';
        enum 'control';
        enum 'transaction';
        enum 'core';
    }

    // ── Definitions from AFO ────────────────────────────────────────────────
    // Generated from kgrapher/ontologies/afo.ttl and afo-maf-mapping.tsv by
    // cmd/mafgen; each definition's doc is AFO's comment for the term.
    // @generated

    // ── Units the standard library lacks ────────────────────────────────────
    // Units the systems declare that are not in the SysML v2 Quantities and
    // Units library (release 2026-08), defined from it with the factors the
    // framework converts with (mbaigo usecases/qudt.go). Referenced by
    // mbaigo's usecases/sysml_units.go as mAF::<name>.
    attribute <ms> millisecond : ISQ::DurationUnit {
        :>> unitConversion : MeasurementReferences::ConversionByPrefix { :>> prefix = SIPrefixes::milli; :>> referenceUnit = SI::s; }
    }
    attribute <ftn> fortnight : ISQ::DurationUnit {
        :>> unitConversion : MeasurementReferences::ConversionByConvention { :>> referenceUnit = SI::s; :>> conversionFactor = 1209600; }
    }
    attribute <hPa> hectopascal : ISQ::PressureUnit {
        :>> unitConversion : MeasurementReferences::ConversionByPrefix { :>> prefix = SIPrefixes::hecto; :>> referenceUnit = SI::Pa; }
    }
    attribute <kPa> kilopascal : ISQ::PressureUnit {
        :>> unitConversion : MeasurementReferences::ConversionByPrefix { :>> prefix = SIPrefixes::kilo; :>> referenceUnit = SI::Pa; }
    }
    attribute <bar> bar : ISQ::PressureUnit {
        :>> unitConversion : MeasurementReferences::ConversionByConvention { :>> referenceUnit = SI::Pa; :>> conversionFactor = 1E5; }
    }
    attribute <mbar> millibar : ISQ::PressureUnit {
        :>> unitConversion : MeasurementReferences::ConversionByPrefix { :>> prefix = SIPrefixes::milli; :>> referenceUnit = bar; }
    }
    attribute <fur> furlong : ISQ::LengthUnit {
        :>> unitConversion : MeasurementReferences::ConversionByConvention { :>> referenceUnit = SI::m; :>> conversionFactor = 201.168; }
    }
    attribute <r> revolution : ISQ::AngularMeasureUnit {
        :>> unitConversion : MeasurementReferences::ConversionByConvention { :>> referenceUnit = SI::rad; :>> conversionFactor = 6.283185307179586; :>> isExact = false; }
    }
    attribute <gon> gon : ISQ::AngularMeasureUnit {
        :>> unitConversion : MeasurementReferences::ConversionByConvention { :>> referenceUnit = SI::rad; :>> conversionFactor = 1.5707963267948967E-2; :>> isExact = false; }
    }
    attribute <'%'> percent : MeasurementReferences::DimensionOneUnit {
        :>> unitConversion : MeasurementReferences::ConversionByConvention { :>> referenceUnit = MeasurementReferences::one; :>> conversionFactor = 1E-2; }
    }
    attribute <ppm> 'part per million' : MeasurementReferences::DimensionOneUnit {
        :>> unitConversion : MeasurementReferences::ConversionByConvention { :>> referenceUnit = MeasurementReferences::one; :>> conversionFactor = 1E-6; }
    }
    attribute <'r/min'> 'revolution per minute' : ISQ::AngularVelocityUnit = r / SI::min;
    attribute <'mm/h'> 'millimetre per hour' : ISQ::SpeedUnit = SI::mm / SI::h;
    attribute <'fur/ftn'> 'furlong per fortnight' : ISQ::SpeedUnit = fur / ftn;
}
